# Software Requirement Specification (SRS) Template

# Specification: Specification Document
- Description: Requirements Document

## R4 (Header 1)
Software Requirement Specification
- Type: Header

## R5 (Information)
Project: <Project>
Author: <Author>
State: <Draft/Proposed/Released>
Version: <0.1>
Date: <05-03-2014>
- Type: Information

## R6 (Header 1)
1. Introduction
- Type: Header

### R7 (Header 2)
1.1 Purpose
- Type: Header

#### R8 (Information)
This document will describe all Software Requirements for the <module_name> module. The first chapters will give an outline on the functionality the module will provide. Additionaly an overview will be given of the context of the module, such as the system it will operate in and modules it will interact with.
- Type: Information

### R9 (Header 2)
1.2 Scope
- Type: Header

#### R10 (Information)
The scope of this specification includes all requirements needed for development of the module. This includes functional, non-functional and safety requirements. Constraints on design and implementation are also included.
Technical solutions are not part of this document, as they will be covered in later stages of development. Test criteria however, are to be documented with each requirement to ensure the testeability.
- Type: Information

## R11 (Header 1)
2. Overall description
- Type: Header

### R12 (Header 2)
2.1 System overview
- Type: Header

#### R13 (Information)
<Describe the system in which the module (for which this specification is) will operate. Depending on the module, you might need to start with a complete system description (i.e. a complete transmission, overview of an engine, etc) or you might suffice with just an overview of the basic software or application software.
Make sure you provide enough context so the reader can understand the context in which the module has to operate, so that when you next describe the functionality of the new module, it will make sense.>
- Type: Information

### R14 (Header 2)
2.2 Module context
- Type: Header

#### R15 (Information)
<Describe the context around the module. I.e., what modules does it interact with, from where will it get inputs and what modules will use its output. This can be done with pictures or extracts from the Software Architecture if it is already known.>
- Type: Information

### R16 (Header 2)
2.3 Module functionality
- Type: Header

#### R17 (Information)
<Give an overview of the functionality (could be a User Story) that the module will provide. Do not go into technical sollutions, but describe the module as if it were black box.>
- Type: Information

### R18 (Header 2)
2.4 Use cases
- Type: Header

#### R19 (Information)
<Describe the use cases of the module. This will provide the reader insight in the different scenario's the module will be used under and what its expected behaviour under these scenario's is.>
- Type: Information

### R20 (Header 2)
2.5 Assumptions and dependencies
- Type: Header

#### R21 (Information)
<Describe any assumptions that are made on the module or its operation.>
<Describe dependencies on other modules, components or systems.>
- Type: Information

## R22 (Header 1)
3. Software Requirements
- Type: Header

### R23 (Information)
This chapter documents all requirements on the described module.
- Type: Information

### R24 (Header 2)
3.1 Interface Requirements
- Type: Header

#### R26 (Information)
The interface requirements document which external interface the module needs to provide or accept. It is split over the categories "Hardware Interfaces", "Software Interfaces" and "Communication Protocols".
- Type: Information

#### R27 (Header 3)
3.1.1 Software Interfaces
- Type: Header

##### R29 (Information)
<Start inserting Software Interface Requirements here.>

#### R30 (Header 3)
3.1.2 Hardware Interfaces
- Type: Header

##### R31 (Information)
<Start inserting Hardware Interface requirements here>

#### R32 (Header 3)
3.1.3 Communication Protocols
- Type: Header

##### R33 (Information)
<Start inserting communication protocol (CAN, LIN, etc) requirements here>

### R34 (Header 2)
3.2 Functional Requirements
- Type: Header

#### R35 (Information)
The functional requirements describe what functions are desired from the module, which actions should lead to what results, etc.
- Type: Information

#### R36 (Header 3)
3.2.1  [ Function/Feature Name (I.e. Downshifting, EGR Control, Clutch actuation, etc) ]
- Type: Header

##### R37 (Information)
<Start inserting functional requirements here>

### R38 (Header 2)
3.3 Non-Functional Requirements
- Type: Header

#### R39 (Information)
This chapter describes the non-functional requirements on the module, such as quality requirements, stability requirements, performance requirements and security requirements.
- Type: Information

#### R40 (Header 3)
3.3.1  [ Quality Requirements / Performance Requirements / Stability Requirements / ....  ]
- Type: Header

##### R41 (Information)
<Start inserting non-functional requirements for the chapter here>

### R42 (Header 2)
3.4 Safety Requirements
- Type: Header

#### R43 (Information)
This chapter documents all Functional Safety requirements for the module, as per the project Safety Plan.
- Type: Information

#### R44 (Header 3)
3.4.1 [ Safety Function X ]
- Type: Header

##### R45 (Information)
<Start inserting safety requirements for the Safety Function X here>

## R46 (Header 1)
4. Terms, Definitions and References
- Type: Header

### R47 (Information)
This chapter will provide a list of terms, definitions and abbreviations as well as a list of references.
- Type: Information

### R48 (Header 2)
4.1 Terms, definitions and abbreviations
- Type: Header

#### R49 (Information)
<Insert table of terms, abbreviations and definitions here. This is best done (and stored) in Word at the moment, since ProR doesn't support editing of tables yet. You can copy-paste tables from word however.>
- Type: Information

### R50 (Header 2)
4.2 References
- Type: Header

#### R51 (Information)
<Provide a list of references to other relevant or dependant documents, diagrams, models, etc>
- Type: Information

## REQ-1 (Requirement Type)
Start editing here.

## SW-MOD-2 (Requirement Type)

## R3 (Header 1)

## R25 (Information)
- Type: Information

## SW-MOD-3 (Requirement Type)
